# -*- coding: utf-8 -*-

# Macro Begin: /home/husky/huskyprojects/freecad/ashtray/extrude.FCMacro +++++++++++++++++++++++++++++++++++++++++++++++++
import FreeCAD
import Part

# Gui.runCommand('Std_DlgMacroRecord',0)
# Gui.runCommand('Part_Extrude',0)
App.getDocument('Part_Cleaned').addObject('Part::Extrusion','Extrude')
f = App.getDocument('Part_Cleaned').getObject('Extrude')
f.Base = App.getDocument('Part_Cleaned').getObject('new_box_cs')
f.DirMode = "Custom"
f.Dir = App.Vector(1.000000000000000, 0.000000000000000, 0.000000000000000)
f.DirLink = None
f.LengthFwd = 2.000000000000000
f.LengthRev = 0.000000000000000
f.Solid = True
f.Reversed = False
f.Symmetric = True
f.TaperAngle = 0.000000000000000
f.TaperAngleRev = 0.000000000000000
# App.getDocument('Part_Cleaned').getObject('Extrude').ViewObject.ShapeAppearance=getattr(App.getDocument('Part_Cleaned').getObject('new_box_cs').getLinkedObject(True).ViewObject,'ShapeAppearance',App.getDocument('Part_Cleaned').getObject('Extrude').ViewObject.ShapeAppearance)
# App.getDocument('Part_Cleaned').getObject('Extrude').ViewObject.LineColor=getattr(App.getDocument('Part_Cleaned').getObject('new_box_cs').getLinkedObject(True).ViewObject,'LineColor',App.getDocument('Part_Cleaned').getObject('Extrude').ViewObject.LineColor)
# App.getDocument('Part_Cleaned').getObject('Extrude').ViewObject.PointColor=getattr(App.getDocument('Part_Cleaned').getObject('new_box_cs').getLinkedObject(True).ViewObject,'PointColor',App.getDocument('Part_Cleaned').getObject('Extrude').ViewObject.PointColor)
App.getDocument('Part_Cleaned').getObject('new_box_cs').Visibility = False
App.ActiveDocument.recompute()
# Macro End: /home/husky/huskyprojects/freecad/ashtray/extrude.FCMacro +++++++++++++++++++++++++++++++++++++++++++++++++
